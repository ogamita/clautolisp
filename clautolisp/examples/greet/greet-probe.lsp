(defun c:greet-probe (/ id status)
  (princ "\n[probe] entering c:greet-probe")
  ;; Relative name: run from this directory (see greet.lsp).
  (setq id (load_dialog "greet.dcl"))
  (princ (strcat "\n[probe] load_dialog -> " (itoa id)))
  (cond
    ((< id 0) (princ "\n[probe] FAILED: bad load_dialog"))
    (T
     (princ "\n[probe] calling new_dialog...")
     (princ (strcat "\n[probe] new_dialog -> " (vl-prin1-to-string (new_dialog "greet" id))))
     (princ "\n[probe] calling set_tile...")
     (set_tile "name" "World")
     (princ "\n[probe] calling action_tile accept...")
     (action_tile "accept" "(done_dialog 1)")
     (princ "\n[probe] calling action_tile cancel...")
     (action_tile "cancel" "(done_dialog 0)")
     (princ "\n[probe] calling start_dialog (this BLOCKS until you click OK/Cancel)...")
     (setq status (start_dialog))
     (princ (strcat "\n[probe] start_dialog -> " (itoa status)))
     (unload_dialog id)
     (princ "\n[probe] done.")))
  (princ))
(c:greet-probe)
(exit)
