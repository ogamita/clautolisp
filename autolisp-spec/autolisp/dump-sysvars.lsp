;;;; dump-sysvars.lsp -- dump every system variable and its current
;;;; value to a file, one variable per line.
;;;;
;;;; Companion utility to alref.lsp. Loadable into any conforming
;;;; AutoLISP implementation (AutoCAD, BricsCAD, clautolisp).
;;;;
;;;; Entry point:
;;;;
;;;;   (dump-sysvars "sysvars.txt")
;;;;       Write one line per system variable to FILENAME, in the
;;;;       form
;;;;
;;;;           "NAME" VALUE
;;;;
;;;;       where both NAME and VALUE are emitted with PRIN1 (not
;;;;       PRINC), so string values keep their surrounding quotes and
;;;;       the file is re-readable. Returns the number of variables
;;;;       written, or nil if FILENAME could not be opened.
;;;;
;;;;   (dump-sysvars-names)
;;;;       Return the list of system-variable names this utility
;;;;       knows about (already sorted lexicographically).
;;;;
;;;; Why an embedded name list?
;;;;
;;;; Stock AutoLISP offers no primitive that enumerates the system
;;;; variables: (getvar name) reads one variable by name, but there is
;;;; no (getvars) or apropos-style listing. So, as specified, the
;;;; name list is taken from the documented inventory in
;;;; autolisp-spec/documentation/system-variables-inventory.sexp and
;;;; embedded here, sorted lexicographically (ASCII / C collation) by
;;;; variable name.
;;;;
;;;; (getvar "NAME") returns nil for a variable the running host does
;;;; not implement; such variables still produce a line, with a nil
;;;; value.
;;;;
;;;; Portable across AutoCAD / BricsCAD / clautolisp: uses only the
;;;; strict-subset primitives (open, close, prin1, princ, terpri,
;;;; getvar, foreach, basic list ops). No vl-string-*, no
;;;; host-specific extensions.

;; Library version. Format is MAJOR.MINOR.DEVELOP, matching the
;; clautolisp / alref convention. Bump the DEVELOP counter on every
;; change that touches this file's behaviour.
(setq *dump-sysvars-version* "1.0.0")

(defun dump-sysvars-version ( )
  "Return the dump-sysvars.lsp library version as a string."
  *dump-sysvars-version*)

;; The documented system-variable names, sorted lexicographically.
;; Sourced from system-variables-inventory.sexp; see file header.
(setq *dump-sysvars-names*
  (list
    "3DCONVERSIONMODE" "3DDWFPREC" "3DOSMODE" "3DSELECTIONMODE"
    "ACADLSPASDOC" "ACADPREFIX" "ACADVER" "ACISHLRRESOLUTION"
    "ACISOUTVER" "ACISSAVEASMODE" "ACTIVITYINSIGHTSPATH" "ACTIVITYINSIGHTSSTATE"
    "ACTIVITYINSIGHTSSUPPORT" "ACTIVITYINSIGHTSVIEWEDLOGGING" "ACTPATH" "ACTRECORDERSTATE"
    "ACTRECPATH" "ACTUI" "ADAPTIVEGRIDSTEPSIZE" "ADCSTATE"
    "AFLAGS" "ALIGNDIMENSIONONISOMETRIC" "ALLOWEDBENDANGLES" "ALLOWTABEXTERNALMOVE"
    "ALLOWTABMOVE" "ALLOWTABSPLIT" "AMPOWERDIMDISPLAY" "AMSYMSCALE"
    "ANGBASE" "ANGDIR" "ANNOALLVISIBLE" "ANNOAUTOSCALE"
    "ANNOMONITOR" "ANNOSCALEZOOM" "ANNOTATIVEDWG" "ANTIALIASRENDER"
    "ANTIALIASSCREEN" "APBOX" "APERTURE" "APPAUTOLOAD"
    "APPLYGLOBALOPACITIES" "APSTATE" "AREA" "AREAPREC"
    "AREAUNITS" "ARRAYASSOCIATIVITY" "ARRAYEDITSTATE" "ARRAYTYPE"
    "ASSISTANTSTATE" "ATTDIA" "ATTFULLUPDATE" "ATTIPE"
    "ATTMODE" "ATTMULTI" "ATTRACTIONDISTANCE" "ATTREQ"
    "AUDITCTL" "AUDITERRORCOUNT" "AUNITS" "AUPREC"
    "AUTOCOMPLETEDELAY" "AUTOCOMPLETEMODE" "AUTODWFPUBLISH" "AUTOMATICCONNECTION"
    "AUTOMATICPUB" "AUTOMATICSTAIRSECTIONBEHAVIOR" "AUTOMATICTEES" "AUTOPLACEMENT"
    "AUTORESETSCALES" "AUTOSAVECHECKSONLYFIRSTBITDBMOD" "AUTOSNAP" "AUTOTRACKINGVECCOLOR"
    "AUTOVPFITTING" "BACKGROUNDPLOT" "BACKZ" "BACTIONBARMODE"
    "BACTIONCOLOR" "BASEFILE" "BCFSOURCEURL" "BCONSTATUSMODE"
    "BCONVERTLAYER" "BDEPENDENCYHIGHLIGHT" "BEDITASSOCMODE" "BGCOREPUBLISH"
    "BGRIPOBJCOLOR" "BGRIPOBJSIZE" "BILLOFMATERIALSSETTINGS" "BIMDEFAULTPROPERTIESPATH"
    "BIMMATCHPROP" "BIMOSMODE" "BIMPROFILESTANDARDS" "BINDTYPE"
    "BKGCOLOR" "BKGCOLORPS" "BLIPMODE" "BLOCKCREATEMODE"
    "BLOCKEDITLOCK" "BLOCKEDITOR" "BLOCKEXCLUDECOLOR" "BLOCKIFYMODE"
    "BLOCKIFYTOLERANCE" "BLOCKINCLUDECOLOR" "BLOCKLEVELOFDETAIL" "BLOCKMRULIST"
    "BLOCKNAVIGATE" "BLOCKREDEFINEMODE" "BLOCKSDATACOLLECTION" "BLOCKSPATH"
    "BLOCKSRECENTFOLDER" "BLOCKSTATE" "BLOCKSYNCFOLDER" "BLOCKTARGETCOLOR"
    "BLOCKTESTWINDOW" "BMAUTOUPDATE" "BMEXTERNALIZEILLEGALSYMBOLS" "BMFORMTEMPLATEPATH"
    "BMTOOLPATH" "BMUPDATEMODE" "BOLTINGASMDEFAULTLENGTHINCREMENT" "BOLTINGASMDEFAULTNUT"
    "BOLTINGASMDEFAULTNUTSNUMBER" "BOLTINGASMDEFAULTSTUD" "BOMFILTERSETTINGS" "BOMPROPERTYSET"
    "BOMTEMPLATE" "BOMTHUMBNAILHEIGHT" "BOMTHUMBNAILWIDTH" "BOUNDARYCOLOR"
    "BPARAMETERCOLOR" "BPARAMETERFONT" "BPARAMETERSIZE" "BPTEXTHORIZONTAL"
    "BSEARCHINCLUDEEXISTINGBLOCKS" "BSYSLIBCOPYOVERWRITE" "BTMARKDISPLAY" "BVMODE"
    "CACHELAYOUT" "CACHEMAXFILES" "CACHEMAXTOTALSIZE" "CALCINPUT"
    "CAMERADISPLAY" "CAMERAHEIGHT" "CANNOSCALE" "CANNOSCALEVALUE"
    "CAPTURETHUMBNAILS" "CBARTRANSPARENCY" "CCONSTRAINTFORM" "CDATE"
    "CECOLOR" "CELTSCALE" "CELTYPE" "CELWEIGHT"
    "CENTERCROSSGAP" "CENTERCROSSSIZE" "CENTEREXE" "CENTERLAYER"
    "CENTERLTSCALE" "CENTERLTYPE" "CENTERLTYPEFILE" "CENTERMARKEXE"
    "CENTERMT" "CETRANSPARENCY" "CGEOCS" "CHAMFERA"
    "CHAMFERB" "CHAMFERC" "CHAMFERD" "CHAMMODE"
    "CHECKDWLPRESENCE" "CIRCLERAD" "CIRCULARARROWHEADLENGTH" "CIRCULARARROWHEADWIDTH"
    "CIRCULARARROWLEADERRADIUS" "CIRCULARARROWLEADERROTATION" "CIRCULARARROWTHICKNESS" "CLAYER"
    "CLAYOUT" "CLEANSCREENOPTIONS" "CLEANSCREENSTATE" "CLIPBOARDFORMAT"
    "CLIPBOARDFORMATS" "CLIPROMPTLINES" "CLIPROMPTUPDATE" "CLISTATE"
    "CLOSECHECKSONLYFIRSTBITDBMOD" "CLOUDDOWNLOADPATH" "CLOUDLOG" "CLOUDLOGVERBOSE"
    "CLOUDONMODIFIED" "CLOUDSERVER" "CLOUDSSOCLIENTID" "CLOUDSSOSCOPE"
    "CLOUDTEMPFOLDER" "CLOUDUPLOADDEPENDENCIES" "CMATERIAL" "CMDACTIVE"
    "CMDDIA" "CMDECHO" "CMDINPUTHISTORYMAX" "CMDLINEEDITBGCOLOR"
    "CMDLINEEDITFGCOLOR" "CMDLINEFADINGLOGBGCOLOR" "CMDLINEFADINGLOGFADEDELAY" "CMDLINEFADINGLOGFGCOLOR"
    "CMDLINEFADINGLOGTRANSPARENCY" "CMDLINEFONTNAME" "CMDLINEFONTSIZE" "CMDLINEFRAMEACTIVETRANSPARENCY"
    "CMDLINEFRAMEINACTIVETRANSPARENCY" "CMDLINEFRAMEUSETEXTSCR" "CMDLINELISTBGCOLOR" "CMDLINELISTFGCOLOR"
    "CMDLINEOPTIONBGCOLOR" "CMDLINEOPTIONSHORTCUTCOLOR" "CMDLINEUSEMINIFRAME" "CMDLNTEXT"
    "CMDNAMES" "CMFADECOLOR" "CMFADEOPACITY" "CMLEADERSTYLE"
    "CMLJUST" "CMLSCALE" "CMLSTYLE" "CMOSNAP"
    "CMPCLRMISS" "CMPCLRMOD1" "CMPCLRMOD2" "CMPCLRNEW"
    "CMPDIFFLIMIT" "CMPFADECTL" "CMPLOG" "COLORBOOKPATH"
    "COLORPICKBOX" "COLORTHEME" "COLORX" "COLORY"
    "COLORZ" "COMACADCOMPATIBILITY" "COMBINETEXTMODE" "COMMANDASSIST"
    "COMMANDMACROSSTATE" "COMMANDPREVIEW" "COMMENTHIGHLIGHT" "COMMUNICATORBACKGROUNDMODE"
    "COMMUNICATORPATH" "COMPARECOLOR1" "COMPARECOLOR2" "COMPARECOLORCOMMON"
    "COMPAREFRONT" "COMPAREHATCH" "COMPAREPROPS" "COMPARERCMARGIN"
    "COMPARERCSHAPE" "COMPARESHOW1" "COMPARESHOW2" "COMPARESHOWCOMMON"
    "COMPARESHOWCONTEXT" "COMPARESHOWRC" "COMPARETEXT" "COMPARETOLERANCE"
    "COMPASS" "COMPLEXLTPREVIEW" "COMPONENTSCONFIG" "COMPONENTSPATH"
    "CONSTRAINTBARDISPLAY" "CONSTRAINTBARMODE" "CONSTRAINTINFER" "CONSTRAINTNAMEFORMAT"
    "CONSTRAINTSOLVEMODE" "CONTINUOUSMOTION" "CONVERTODMAX" "CONVERTODMIN"
    "CONVERTTHMAX" "CONVERTTHMIN" "COORDS" "COPYGUIDED3DDISPLAYSOURCEFACES"
    "COPYMODE" "COUNTCHECK" "COUNTCOLOR" "COUNTERRORCOLOR"
    "COUNTERRORNUM" "COUNTNUMBER" "COUNTPALETTESTATE" "COUNTSERVICE"
    "CPLOTSTYLE" "CPROFILE" "CRASHREPORTSENDING" "CREATESKETCHFEATURE"
    "CREATETHUMBNAILONTHEFLY" "CREATEVIEWPORTS" "CROSSHAIRDRAWMODE" "CROSSINGAREACOLOR"
    "CTAB" "CTABLESTYLE" "CTRL3DMOUSE" "CTRLMBUTTON"
    "CTRLMOUSE" "CULLINGOBJ" "CULLINGOBJSELECTION" "CURSORBADGE"
    "CURSORMODE" "CURSORSIZE" "CURSORTYPE" "CVALLOWBREAKLINECROSSINGS"
    "CVANGLESAMPLINGINTERVAL" "CVARCTESSELLATIONGRADING" "CVARCTESSELLATIONSURFACE" "CVARCTESSELLATIONTEMPLATEELEMENT"
    "CVASSOCIATIVITY" "CVDEFAULTCURVETYPEHA" "CVDEFAULTCURVETYPEVA" "CVELEVATIONATBREAKLINECROSSINGS"
    "CVERSIONCONTROLPATH" "CVGRADEUNIT" "CVGRADEUNITPREC" "CVIEWDETAILSTYLE"
    "CVLENGTHSAMPLINGINTERVAL" "CVPORT" "CVSLOPEUNIT" "CVSLOPEUNITPREC"
    "CVSTATIONUNIT" "CVSTATIONUNITPREC" "DATACOLLECTION" "DATACOLLECTIONENABLED"
    "DATACOLLECTIONLOGINTYPE" "DATACOLLECTIONOPTIONS" "DATALINKNOTIFY" "DATE"
    "DBCSTATE" "DBLCLKEDIT" "DBMOD" "DCTCUST"
    "DCTMAIN" "DEFAULTBSYSLIBIMPERIAL" "DEFAULTBSYSLIBMETRIC" "DEFAULTGIZMO"
    "DEFAULTLIGHTING" "DEFAULTLIGHTINGTYPE" "DEFAULTLIGHTSHADOWBLUR" "DEFAULTNEWSHEETTEMPLATE"
    "DEFAULTPLOTSTYLETABLE" "DEFAULTSPACEHEIGHT" "DEFAULTSTORYNAMINGSCHEME" "DEFAULTSTYLEPIPECROSS"
    "DEFAULTSTYLEPIPEECCENTRICREDUCER" "DEFAULTSTYLEPIPEELBOW45" "DEFAULTSTYLEPIPEELBOW90" "DEFAULTSTYLEPIPEREDUCER"
    "DEFAULTSTYLEPIPESEGMENT" "DEFAULTSTYLEPIPETEE" "DEFLPLSTYLE" "DEFPLSTYLE"
    "DELETETOOL" "DELOBJ" "DEMANDLOAD" "DETAILSPATH"
    "DGNEXPXREFMODE" "DGNFRAME" "DGNIMP2DCLOSEDBSPLINECURVEIMPORTMODE" "DGNIMP2DELLIPSEIMPORTMODE"
    "DGNIMP2DSHAPEIMPORTMODE" "DGNIMP3DCLOSEDBSPLINECURVEIMPORTMODE" "DGNIMP3DELLIPSEIMPORTMODE" "DGNIMP3DOBJECTIMPORTMODE"
    "DGNIMP3DSHAPEIMPORTMODE" "DGNIMPBREAKDIMENSIONASSOCIATION" "DGNIMPCONVERTDGNCOLORINDICESTOTRUECOLORS" "DGNIMPCONVERTEMPTYDATAFIELDSTOSPACES"
    "DGNIMPERASEUNUSEDRESOURCES" "DGNIMPEXPLODETEXTNODES" "DGNIMPIMPORTACTIVEMODELTOMODELSPACE" "DGNIMPIMPORTDGTEXTSASDBMTEXTS"
    "DGNIMPIMPORTINVISIBLEELEMENTS" "DGNIMPIMPORTPAPERSPACEMODELS" "DGNIMPIMPORTVIEWINDEX" "DGNIMPORTMAX"
    "DGNIMPORTMODE" "DGNIMPRECOMPUTEDIMENSIONSAFTERIMPORT" "DGNIMPSYMBOLRESOURCEFILES" "DGNIMPXREFIMPORTMODE"
    "DGNMAPPINGPATH" "DGNOSNAP" "DIASTAT" "DIMADEC"
    "DIMALT" "DIMALTD" "DIMALTF" "DIMALTRND"
    "DIMALTTD" "DIMALTTZ" "DIMALTU" "DIMALTZ"
    "DIMANNO" "DIMAPOST" "DIMARCSYM" "DIMASO"
    "DIMASSOC" "DIMASZ" "DIMATFIT" "DIMAUNIT"
    "DIMAZIN" "DIMBLK" "DIMBLK1" "DIMBLK2"
    "DIMCEN" "DIMCLRD" "DIMCLRE" "DIMCLRT"
    "DIMCONSTRAINTICON" "DIMCONTINUEMODE" "DIMDEC" "DIMDLE"
    "DIMDLI" "DIMDSEP" "DIMEXE" "DIMEXO"
    "DIMFIT" "DIMFRAC" "DIMFXL" "DIMFXLON"
    "DIMGAP" "DIMJOGANG" "DIMJUST" "DIMLAYER"
    "DIMLDRBLK" "DIMLFAC" "DIMLIM" "DIMLTEX1"
    "DIMLTEX2" "DIMLTYPE" "DIMLUNIT" "DIMLWD"
    "DIMLWE" "DIMMARKTYPE" "DIMPICKBOX" "DIMPOST"
    "DIMRND" "DIMSAH" "DIMSCALE" "DIMSD1"
    "DIMSD2" "DIMSE1" "DIMSE2" "DIMSHO"
    "DIMSOXD" "DIMSTYLE" "DIMTAD" "DIMTDEC"
    "DIMTFAC" "DIMTFILL" "DIMTFILLCLR" "DIMTIH"
    "DIMTIX" "DIMTM" "DIMTMOVE" "DIMTOFL"
    "DIMTOH" "DIMTOL" "DIMTOLJ" "DIMTP"
    "DIMTSZ" "DIMTVP" "DIMTXSTY" "DIMTXT"
    "DIMTXTDIRECTION" "DIMTXTRULER" "DIMTZIN" "DIMUNIT"
    "DIMUPT" "DIMZIN" "DISPLAYAXES" "DISPLAYAXESFORMEP"
    "DISPLAYSCALING" "DISPLAYSIDESANDENDS" "DISPLAYSNAPMARKERINALLVIEWS" "DISPLAYTOOLTIPS"
    "DISPLAYTRUEDIMENSION" "DISPPAPERBKG" "DISPPAPERMARGINS" "DISPSILH"
    "DISPSILHBLOCKS" "DISTANCE" "DIVMESHBOXHEIGHT" "DIVMESHBOXLENGTH"
    "DIVMESHBOXWIDTH" "DIVMESHCONEAXIS" "DIVMESHCONEBASE" "DIVMESHCONEHEIGHT"
    "DIVMESHCYLAXIS" "DIVMESHCYLBASE" "DIVMESHCYLHEIGHT" "DIVMESHPYRBASE"
    "DIVMESHPYRHEIGHT" "DIVMESHPYRLENGTH" "DIVMESHSPHEREAXIS" "DIVMESHSPHEREHEIGHT"
    "DIVMESHTORUSPATH" "DIVMESHTORUSSECTION" "DIVMESHWEDGEBASE" "DIVMESHWEDGEHEIGHT"
    "DIVMESHWEDGELENGTH" "DIVMESHWEDGESLOPE" "DIVMESHWEDGEWIDTH" "DMAUDITLEVEL"
    "DMAUTOUPDATE" "DMCONNECTIONCUTTYPE" "DMPUSHPULLSUBTRACT" "DMRECOGNIZE"
    "DOCKPRIORITY" "DOCTABPOSITION" "DONUTID" "DONUTOD"
    "DRAGMODE" "DRAGMODECONSTRAINTS" "DRAGMODEFACES" "DRAGMODEHIDE"
    "DRAGMODEINTERRUPT" "DRAGOPEN" "DRAGP1" "DRAGP2"
    "DRAGSNAP" "DRAGVS" "DRAWINGPATH" "DRAWINGVIEWASM"
    "DRAWINGVIEWENTS" "DRAWINGVIEWFLAGS" "DRAWINGVIEWPRESET" "DRAWINGVIEWPRESETHIDDEN"
    "DRAWINGVIEWPRESETSCALE" "DRAWINGVIEWPRESETTANGENT" "DRAWINGVIEWPRESETTRAILING" "DRAWINGVIEWQUALITY"
    "DRAWORDERCTL" "DRSTATE" "DWFFORMAT" "DWFFRAME"
    "DWFOSNAP" "DWFVERSION" "DWGCHECK" "DWGCODEPAGE"
    "DWGGUIDCLOUDAI" "DWGNAME" "DWGPREFIX" "DWGTITLED"
    "DX12FRAMERATEUNLIMITED" "DXEVAL" "DXFTEXTADJUSTALIGNMENT" "DYNCONSTRAINTMODE"
    "DYNDIGRIP" "DYNDIMAPERTURE" "DYNDIMCOLORHOT" "DYNDIMCOLORHOVER"
    "DYNDIMDISTANCE" "DYNDIMLINETYPE" "DYNDIVIS" "DYNINFOTIPS"
    "DYNINPUTTRANSPARENCY" "DYNMODE" "DYNPICOORDS" "DYNPIFORMAT"
    "DYNPIVIS" "DYNPROMPT" "DYNTOOLTIPS" "EDGEMODE"
    "ELEVATION" "ENABLEATTRACTION" "ENABLEBIMBKUPDATE" "ENABLEHYPERLINKMENU"
    "ENABLEHYPERLINKTOOLTIP" "ENABLESYNCPDF" "ENTERPRISEMENU" "ERHIGHLIGHT"
    "ERRNO" "ERSTATE" "EXPERIMENTALMODE" "EXPERIMENTALONSTARTPAGE"
    "EXPERT" "EXPINSALIGN" "EXPINSANGLE" "EXPINSFIXANGLE"
    "EXPINSFIXSCALE" "EXPINSSCALE" "EXPLMODE" "EXPORT3DPDFWRITER"
    "EXPORTACISASSEMBLYWRITER" "EXPORTACISFORMATVERSION" "EXPORTCATIAV4FORMATVERSION" "EXPORTCATIAV5FORMATVERSION"
    "EXPORTEPLOTFORMAT" "EXPORTGEOMETRYFLAGS" "EXPORTHIDDENPARTS" "EXPORTMODELSPACE"
    "EXPORTPAGESETUP" "EXPORTPAPERSPACE" "EXPORTPARASOLIDFORMATVERSION" "EXPORTPRODUCTSTRUCTURE"
    "EXPORTSTEPFORMATVERSION" "EXPORTXCGMFORMATVERSION" "EXPVALUE" "EXPWHITEBALANCE"
    "EXTMAX" "EXTMIN" "EXTNAMES" "EXTRUDEINSIDE"
    "EXTRUDEOUTSIDE" "FACETERDEVNORMAL" "FACETERDEVSURFACE" "FACETERMAXEDGELENGTH"
    "FACETERMAXGRID" "FACETERMESHTYPE" "FACETERMINVGRID" "FACETERPRIMITIVEMODE"
    "FACETERSMOOTHLEV" "FACETRATIO" "FACETRES" "FASTSHADEDMODE"
    "FBXEXPORTCAMERAS" "FBXEXPORTENTITIES" "FBXEXPORTENTITIESSELTYPE" "FBXEXPORTLIGHTS"
    "FBXEXPORTMATERIALS" "FBXEXPORTTEXTURES" "FBXEXPORTTEXTURESPATH" "FEATURECOLORS"
    "FIELDDISPLAY" "FIELDEVAL" "FILEDIA" "FILETABPREVIEW"
    "FILETABSTATE" "FILETABTHUMBHOVER" "FILLETPOLYARC" "FILLETRAD"
    "FILLETWELDINGCOMBINEADJACENT" "FILLETWELDINGMAXGAPRATIO" "FILLETWELDINGZSIZE" "FILLMODE"
    "FITLINEFITARCMODE" "FITTINGRADIUSTYPE" "FITTINGRADIUSVALUE" "FLANGEASMDEFAULTGASKET"
    "FONTALT" "FONTMAP" "FRAME" "FRAMESELECTION"
    "FRONTZ" "FULLOPEN" "FULLPLOTPATH" "GALLERYVIEW"
    "GEARTEETHNUMBER" "GENERATEASSOCATTRS" "GENERATEASSOCVIEWS" "GEOCSMAPPRIORITY"
    "GEOLATLONGFORMAT" "GEOLOCATEMODE" "GEOMAPMODE" "GEOMARKERVISIBILITY"
    "GEOMARKPOSITIONSIZE" "GEOMRELATIONS" "GETSTARTED" "GFANG"
    "GFCLR1" "GFCLR2" "GFCLRLUM" "GFCLRSTATE"
    "GFNAME" "GFSHIFT" "GLOBALOPACITY" "GLSWAPMODE"
    "GRADIENTCOLORBOTTOM" "GRADIENTCOLORMIDDLE" "GRADIENTCOLORTOP" "GRADIENTMODE"
    "GRIDAXISCOLOR" "GRIDDISPLAY" "GRIDMAJOR" "GRIDMAJORCOLOR"
    "GRIDMINORCOLOR" "GRIDMODE" "GRIDSTYLE" "GRIDUNIT"
    "GRIDXYZTINT" "GRIPBLOCK" "GRIPCOLOR" "GRIPCONTOUR"
    "GRIPDYNCOLOR" "GRIPHOT" "GRIPHOVER" "GRIPMULTIFUNCTIONAL"
    "GRIPOBJLIMIT" "GRIPS" "GRIPSIZE" "GRIPSUBOBJMODE"
    "GRIPTIPS" "GROUPDISPLAYMODE" "GSDEVICETYPE2D" "GSDEVICETYPE3D"
    "GTAUTO" "GTDEFAULT" "GTLOCATION" "HALOGAP"
    "HANDLES" "HANDSEED" "HELPPREFIX" "HIDEPRECISION"
    "HIDESYSTEMPRINTERS" "HIDETEXT" "HIDEXREFSCALES" "HIGHLIGHT"
    "HIGHLIGHTCOLOR" "HIGHLIGHTEFFECT" "HIGHLIGHT_ALPHA" "HORIZONBKG_ENABLE"
    "HORIZONBKG_GROUNDHORIZON" "HORIZONBKG_GROUNDORIGIN" "HORIZONBKG_SKYHIGH" "HORIZONBKG_SKYHORIZON"
    "HORIZONBKG_SKYLOW" "HOTKEYASSISTANT" "HPANG" "HPANNOTATIVE"
    "HPASSOC" "HPBACKGROUNDCOLOR" "HPBOUND" "HPBOUNDRETAIN"
    "HPCOLOR" "HPDLGMODE" "HPDOUBLE" "HPDRAWMODE"
    "HPDRAWORDER" "HPGAPTOL" "HPISLANDDETECTION" "HPISLANDDETECTIONMODE"
    "HPLAYER" "HPLINETYPE" "HPMAXAREAS" "HPMAXCONTOURPOINTS"
    "HPMAXLINES" "HPNAME" "HPOBJWARNING" "HPORIGIN"
    "HPORIGINMODE" "HPPATHALIGNMENT" "HPPATHWIDTH" "HPPICKMODE"
    "HPQUICKPREVIEW" "HPQUICKPREVTIMEOUT" "HPSCALE" "HPSEPARATE"
    "HPSPACE" "HPTRANSPARENCY" "HYPERLINKBASE" "IBLENVIRONMENT"
    "IFCCREATEUNIQUEGUID" "IFCEXPLODEEXTERNALREFERENCES" "IFCEXPORTAUTHOR" "IFCEXPORTAUTHORIZATION"
    "IFCEXPORTBASEQUANTITIES" "IFCEXPORTELEMENTSONOFFANDFROZENLAYER" "IFCEXPORTIDSPROPERTIESONLY" "IFCEXPORTMAPPINGPATH"
    "IFCEXPORTMULTIPLYELEMENTSASAGGREGATED" "IFCEXPORTORGANIZATION" "IFCEXPORTPROFILECENTEROFGRAVITY" "IFCEXPORTSUBTRACTOPENINGS"
    "IFCEXPORTSWEPTSOLIDSASBREP" "IFCEXPORTTESSELATION" "IFCEXPORTVALIDATEMODEL" "IFCSETTINGSCONFIG"
    "IFCTESSELATEBSPLINECURVESANDSURFACES" "IMAGEASYNC" "IMAGECACHEFOLDER" "IMAGECACHEMAXMEMORY"
    "IMAGEDISKCACHE" "IMAGEFRAME" "IMAGEHLT" "IMAGENOTIFY"
    "IMPLIEDFACE" "IMPORTCATIAV5EDGEATTRIBUTES" "IMPORTCATIAV5REPRESENTATION" "IMPORTCATIAV5SEARCHPATHSPREFERENCE"
    "IMPORTCOLORS" "IMPORTCREOALTERNATESEARCHPATHS" "IMPORTCREOCONFIGURATION" "IMPORTCUIFILEEXISTS"
    "IMPORTHIDDENPARTS" "IMPORTIGESSIMPLIFY" "IMPORTIGESSTITCH" "IMPORTINVENTORALTERNATESEARCHPATHS"
    "IMPORTINVENTORSEARCHPATHSPREFERENCE" "IMPORTJTREPRESENTATION" "IMPORTNXALTERNATESEARCHPATHS" "IMPORTNXCONFIGURATION"
    "IMPORTNXSEARCHPATHSPREFERENCE" "IMPORTPMI" "IMPORTPRODUCTSTRUCTURE" "IMPORTREPAIR"
    "IMPORTSIMPLIFY" "IMPORTSOLIDEDGEALTERNATESEARCHPATHS" "IMPORTSOLIDEDGESEARCHPATHSPREFERENCE" "IMPORTSOLIDWORKSALTERNATESEARCHPATHS"
    "IMPORTSOLIDWORKSCONFIGURATION" "IMPORTSOLIDWORKSREPRESENTATION" "IMPORTSOLIDWORKSROTATEYZ" "IMPORTSOLIDWORKSSEARCHPATHSPREFERENCE"
    "IMPORTSTEPROTATEYZ" "IMPORTSTITCH" "INCLUDEPLOTSTAMP" "INDEXCTL"
    "INETLOCATION" "INPUTHISTORYMODE" "INPUTSEARCHDELAY" "INSBASE"
    "INSNAME" "INSUNITS" "INSUNITSDEFSOURCE" "INSUNITSDEFTARGET"
    "INSUNITSSCALING" "INTELLIGENTUPDATE" "INTERFERECOLOR" "INTERFERELAYER"
    "INTERFERENCELEVEL" "INTERFEREOBJVS" "INTERFEREVPVS" "INTERIORELEVATIONMINLENGTH"
    "INTERIORELEVATIONOFFSET" "INTERSECTEDENTITIES" "INTERSECTIONCOLOR" "INTERSECTIONDISPLAY"
    "ISAVEBAK" "ISAVEPERCENT" "ISOLINES" "JIGZOOMMAX"
    "JIGZOOMMIN" "KEEPCONNECTIONS" "LARGEOBJECTSUPPORT" "LASTANGLE"
    "LASTPOINT" "LASTPROMPT" "LATITUDE" "LAYERDLGMODE"
    "LAYEREVAL" "LAYEREVALCTL" "LAYERFILTERALERT" "LAYERFILTEREXCESS"
    "LAYERMANAGERSTATE" "LAYERNOTIFY" "LAYEROVERRIDEHIGHLIGHT" "LAYERPMODE"
    "LAYLOCKFADECTL" "LAYOUTCREATEVIEWPORT" "LAYOUTREGENCTL" "LAYOUTTAB"
    "LEGACYCODESEARCH" "LEGACYCTRLPICK" "LENGTHUNITS" "LENSLENGTH"
    "LEVELOFDETAIL" "LICFLAGS" "LIGHTGLYPHCOLOR" "LIGHTGLYPHDISPLAY"
    "LIGHTINGUNITS" "LIGHTSINBLOCKS" "LIGHTWEBGLYPHCOLOR" "LIMCHECK"
    "LIMMAX" "LIMMIN" "LINEARARROWHEADLENGTH" "LINEARARROWHEADWIDTH"
    "LINEARARROWTHICKNESS" "LINEARBRIGHTNESS" "LINEARCONTRAST" "LINEFADING"
    "LINEFADINGLEVEL" "LINETYPE3DPLINE" "LISPINIT" "LISPSYS"
    "LOADMECHANICAL2D" "LOCALE" "LOCALROOTPREFIX" "LOCKUI"
    "LOFTANG1" "LOFTANG2" "LOFTMAG1" "LOFTMAG2"
    "LOFTNORMALS" "LOFTPARAM" "LOGFILEMODE" "LOGFILENAME"
    "LOGFILEPATH" "LOGGEDINSTATUS" "LOGINNAME" "LONGITUDE"
    "LOOKFROMDIRECTIONMODE" "LOOKFROMFEEDBACK" "LOOKFROMZOOMEXTENTS" "LTGAPSELECTION"
    "LTSCALE" "LUNITS" "LUPREC" "LWDEFAULT"
    "LWDISPLAY" "LWDISPSCALE" "LWUNITS" "MACROINSIGHTSSUPPORT"
    "MACRONOTIFY" "MACROREC" "MANIPULATOR" "MANIPULATORCOLORTHEME"
    "MANIPULATORDURATION" "MANIPULATORHANDLE" "MANIPULATORSIZE" "MARKUPASSISTMODE"
    "MARKUPPAPERDISPLAY" "MARKUPPAPERTRANSPARENCY" "MARKUPSELECTIONMODE" "MASSPREC"
    "MASSPROPACCURACY" "MASSUNITS" "MATBROWSERSTATE" "MATEDITORSTATE"
    "MAXACTVP" "MAXHATCH" "MAXINTERSECTIONCURVEPOINTS" "MAXSORT"
    "MAXTHREADS" "MBSTATE" "MBUTTONPAN" "MEASUREINIT"
    "MEASUREMENT" "MECH2DSAVEFORMAT" "MECHANICALBLOCKS" "MECHANICALBLOCKSOPTIONS"
    "MECHANICALBROWSERSETTINGS" "MENUBAR" "MENUCTL" "MENUECHO"
    "MENUNAME" "MESHTYPE" "MIDDLECLICKCLOSE" "MILLISECS"
    "MIRRHATCH" "MIRRTEXT" "MLEADERLAYER" "MLEADERSCALE"
    "MODEMACRO" "MSLTSCALE" "MSMSTATE" "MSOLESCALE"
    "MTEXTAUTOSTACK" "MTEXTCOLUMN" "MTEXTDETECTSPACE" "MTEXTED"
    "MTEXTEDENCODING" "MTEXTFIXED" "MTEXTTOOLBAR" "MTFLAGS"
    "MTJIGSTRING" "MULTISELECTANGULARTOLERANCE" "MVIEWPREVIEW" "MYDOCUMENTSPREFIX"
    "NAVBARDISPLAY" "NAVSWHEELMODE" "NAVSWHEELOPACITYBIG" "NAVSWHEELOPACITYMINI"
    "NAVSWHEELSIZEBIG" "NAVSWHEELSIZEMINI" "NAVVCUBEDISPLAY" "NAVVCUBELOCATION"
    "NAVVCUBEOPACITY" "NAVVCUBEORIENT" "NAVVCUBESIZE" "NEARESTDISTANCE"
    "NOMUTT" "NORTHDIRECTION" "OBJECTISOLATIONMODE" "OBSCUREDCOLOR"
    "OBSCUREDLTYPE" "OFFSETDIST" "OFFSETERASE" "OFFSETGAPTYPE"
    "OLEFRAME" "OLEHIDE" "OLEQUALITY" "OLESTARTUP"
    "OPMSTATE" "ORBITAUTOTARGET" "ORTHOMODE" "OSMODE"
    "OSNAPCOORD" "OSNAPNODELEGACY" "OSNAPOVERRIDE" "OSNAPZ"
    "OSOPTIONS" "OVERKILLLAYER" "PALETTEOPAQUE" "PANBUFFER"
    "PANELBUTTONSIZE" "PAPERUPDATE" "PARAMETERCOPYMODE" "PARAMETERMATCHMODE"
    "PARAMETERSSTATUS" "PARAMETRICBLOCKS2DPATH" "PARAMETRIZECONNECTIONS" "PASTESPECMODE"
    "PBLOCKREFERENCEOPERATIONSVISUALIZATION" "PCMSTATE" "PDFANIMATIONFPS" "PDFCACHE"
    "PDFCREATEBOOKMARKS" "PDFEMBEDDEDTTF" "PDFEXPORTHYPERLINKS" "PDFFRAME"
    "PDFIMAGEANTIALIAS" "PDFIMAGECOMPRESSION" "PDFIMAGEDPI" "PDFIMPORTAPPLYLINEWEIGHT"
    "PDFIMPORTASBLOCK" "PDFIMPORTCHARSPACEFACTOR" "PDFIMPORTCOMBINETEXTOBJECTS" "PDFIMPORTCONVERTSOLIDSTOHATCHES"
    "PDFIMPORTFILTER" "PDFIMPORTIMAGEPATH" "PDFIMPORTJOINLINEANDARCSEGMENTS" "PDFIMPORTLAYERS"
    "PDFIMPORTLAYERSUSETYPE" "PDFIMPORTMODE" "PDFIMPORTRASTERIMAGES" "PDFIMPORTSOLIDFILLS"
    "PDFIMPORTSPACEFACTOR" "PDFIMPORTTRUETYPETEXT" "PDFIMPORTTRUETYPETEXTASGEOMETRY" "PDFIMPORTUSECLIPPING"
    "PDFIMPORTUSEGEOMETRYOPTIMIZATION" "PDFIMPORTUSEIMAGECLIPPING" "PDFIMPORTUSEPAGEBORDERCLIPPING" "PDFIMPORTVECTORGEOMETRY"
    "PDFLAYERSSETTING" "PDFLAYOUTSTOEXPORT" "PDFMERGECONTROL" "PDFNOTIFY"
    "PDFOPENINVIEWER" "PDFOSNAP" "PDFPAPERHEIGHT" "PDFPAPERSIZEOVERRIDE"
    "PDFPAPERWIDTH" "PDFPDFA" "PDFPRCCOMPRESSION" "PDFPRCEXPORT"
    "PDFPRCPROJECTION" "PDFPRCVIEWMODE" "PDFSHX" "PDFSHXBESTFONT"
    "PDFSHXLAYER" "PDFSHXTEXTASGEOMETRY" "PDFSHXTHRESHOLD" "PDFSIMPLEGEOMOPTIMIZATION"
    "PDFTTFTEXTASGEOMETRY" "PDFUSEPLOTSTYLES" "PDFVECTORRESOLUTIONDPI" "PDFZOOMTOEXTENTSMODE"
    "PDMODE" "PDSIZE" "PEDITACCEPT" "PELLIPSE"
    "PERIMETER" "PERSPECTIVE" "PERSPECTIVECLIP" "PFACEVMAX"
    "PICKADD" "PICKAUTO" "PICKBOX" "PICKDRAG"
    "PICKFIRST" "PICKSTYLE" "PICTUREEXPORTSCALE" "PLACEMENTSWITCH"
    "PLACESBARFOLDER1" "PLACESBARFOLDER2" "PLACESBARFOLDER3" "PLACESBARFOLDER4"
    "PLATFORM" "PLINECACHE" "PLINECONVERTMODE" "PLINEGCENMAX"
    "PLINEGEN" "PLINEREVERSEWIDTHS" "PLINETYPE" "PLINEWID"
    "PLOTCFGPATH" "PLOTID" "PLOTOFFSET" "PLOTOUTPUTPATH"
    "PLOTROTMODE" "PLOTSTYLEPATH" "PLOTTER" "PLOTTRANSPARENCYOVERRIDE"
    "PLQUIET" "POINTCLOUD2DVSDISPLAY" "POINTCLOUDADAPTIVEDISPLAY" "POINTCLOUDAUTOUPDATE"
    "POINTCLOUDBOUNDARY" "POINTCLOUDCACHEFOLDER" "POINTCLOUDCACHESIZE" "POINTCLOUDCLIPFRAME"
    "POINTCLOUDDENSITY" "POINTCLOUDDOLLHOUSE" "POINTCLOUDEYEDOMELIGHTING" "POINTCLOUDGAPFILLING"
    "POINTCLOUDHSPC" "POINTCLOUDIGNOREGEOTAGS" "POINTCLOUDLIGHTING" "POINTCLOUDLIGHTSOURCE"
    "POINTCLOUDLOCK" "POINTCLOUDLOD" "POINTCLOUDNORMALS" "POINTCLOUDPOINTMAX"
    "POINTCLOUDPOINTMAXLEGACY" "POINTCLOUDPOINTSIZE" "POINTCLOUDRTDENSITY" "POINTCLOUDSHADING"
    "POINTCLOUDVISRETAIN" "POLARADDANG" "POLARANG" "POLARDIST"
    "POLARMODE" "POLYSIDES" "POPERATIONSCOLOR" "POPUPS"
    "PREVIEWCREATIONTRANSPARENCY" "PREVIEWDELAY" "PREVIEWEFFECT" "PREVIEWFILTER"
    "PREVIEWTYPE" "PREVIEWWNDINOPENDLG" "PRINTFILE" "PRINTPDFPREVIEW"
    "PRODUCT" "PROFILEOFFSETBEHAVIOR" "PROGBAR" "PROGRAM"
    "PROJECTAWARE" "PROJECTIONTYPE" "PROJECTLOCATIONVISIBILITY" "PROJECTNAME"
    "PROJECTSEARCHPATHS" "PROJMODE" "PROMPTMENU" "PROMPTMENUFLAGS"
    "PROMPTOPTIONFORMAT" "PROMPTOPTIONTRANSLATEKEYWORDS" "PROPAGATESEARCHSPACE" "PROPAGATETOLERANCE"
    "PROPERTYPREVIEW" "PROPERTYPREVIEWDELAY" "PROPERTYPREVIEWOBJLIMIT" "PROPOBJLIMIT"
    "PROPPREVTIMEOUT" "PROPUNITS" "PROXYGRAPHICS" "PROXYNOTICE"
    "PROXYSERVERENABLED" "PROXYSERVERHTTP" "PROXYSERVERHTTPPORT" "PROXYSERVERHTTPS"
    "PROXYSERVERHTTPSPORT" "PROXYSERVERPASSWORD" "PROXYSERVERUSER" "PROXYSHOW"
    "PROXYWEBSEARCH" "PSLTSCALE" "PSOLHEIGHT" "PSOLWIDTH"
    "PSTYLEMODE" "PSTYLEPOLICY" "PSVPSCALE" "PUBLISHALLSHEETS"
    "PUBLISHCOLLATE" "PUBLISHHATCH" "PUCSBASE" "PUSHTODOCSSTATE"
    "QAFLAGS" "QCSTATE" "QPLOCATION" "QPMODE"
    "QTEXTMODE" "QUADCOMMANDLAUNCH" "QUADDISPLAY" "QUADEXPANDDELAY"
    "QUADEXPANDTABDELAY" "QUADGOTRANSPARENT" "QUADHIDEDELAY" "QUADHIDEMARGIN"
    "QUADICONSIZE" "QUADICONSPACE" "QUADMOSTRECENTITEMS" "QUADPOPUPCORNER"
    "QUADSHOWDELAY" "QUADWIDTH" "QVDRAWINGPIN" "QVLAYOUTPIN"
    "R12SAVEACCURACY" "R12SAVEDEVIATION" "RASTERDPI" "RASTERPERCENT"
    "RASTERPREVIEW" "RASTERTHRESHOLD" "REALTIMESPEEDUP" "REALWORLDSCALE"
    "REBUILD2DCV" "REBUILD2DDEGREE" "REBUILD2DOPTION" "REBUILDDEGREEU"
    "REBUILDDEGREEV" "REBUILDOPTIONS" "REBUILDU" "REBUILDV"
    "RECENTFILES" "RECENTPATH" "RECOVERAUTO" "RECOVERYMODE"
    "REDHILITEFULL_EDGE_ALPHA" "REDHILITEFULL_EDGE_COLOR" "REDHILITEFULL_EDGE_SHOWHIDDEN" "REDHILITEFULL_EDGE_SMOOTHING"
    "REDHILITEFULL_EDGE_THICKNESS" "REDHILITEFULL_FACE_ALPHA" "REDHILITEFULL_FACE_COLOR" "REDHILITEPARTIAL_SELECTEDEDGEGLOW_ALPHA"
    "REDHILITEPARTIAL_SELECTEDEDGEGLOW_COLOR" "REDHILITEPARTIAL_SELECTEDEDGEGLOW_SMOOTHING" "REDHILITEPARTIAL_SELECTEDEDGEGLOW_THICKNESS" "REDHILITEPARTIAL_SELECTEDEDGE_ALPHA"
    "REDHILITEPARTIAL_SELECTEDEDGE_COLOR" "REDHILITEPARTIAL_SELECTEDEDGE_SHOWGLOW" "REDHILITEPARTIAL_SELECTEDEDGE_SMOOTHING" "REDHILITEPARTIAL_SELECTEDEDGE_THICKNESS"
    "REDHILITEPARTIAL_SELECTEDFACE_ALPHA" "REDHILITEPARTIAL_SELECTEDFACE_COLOR" "REDHILITEPARTIAL_UNSELECTEDEDGE_SHOWHIDDEN" "REDHILITE_DUCSLOCKED_FACE_ALPHA"
    "REDHILITE_DUCSLOCKED_FACE_COLOR" "REDHILITE_HIDDENEDGE_ALPHA" "REDHILITE_HIDDENEDGE_COLOR" "REDSDKLINESMOOTHING"
    "REDUCELENGTHTYPE" "REDUCELENGTHVALUE" "REFEDITLOCKNOTINWORKSET" "REFEDITNAME"
    "REFPATHTYPE" "REGENMODE" "REGEXPAND" "REMEMBERFOLDERS"
    "RENDERCOMPOSITIONMATERIAL" "RENDERENVSTATE" "RENDERLEVEL" "RENDERLIGHTCALC"
    "RENDERMATERIALDOWNLOAD" "RENDERMATERIALSPATH" "RENDERPREFSSTATE" "RENDERTARGET"
    "RENDERTIME" "RENDERUSERLIGHTS" "RENDERUSINGHARDWARE" "REPORTERROR"
    "REPORTPANELMODE" "RESTORECONNECTIONS" "RESTORELOSTFOCUS" "RETAINEDGRAPHICS"
    "REVCLOUDAPPROXARCLEN" "REVCLOUDARCSTYLE" "REVCLOUDARCVARIANCE" "REVCLOUDCREATEMODE"
    "REVCLOUDGRIPS" "REVCLOUDLAYER" "REVCLOUDMAXARCLENGTH" "REVCLOUDMINARCLENGTH"
    "REVCLOUDSCALEMODE" "RE_INIT" "RHINOVERSION" "RIBBONBGLOAD"
    "RIBBONCONTEXTSELLIM" "RIBBONDOCKEDHEIGHT" "RIBBONICONRESIZE" "RIBBONPANELMARGIN"
    "RIBBONSELECTMODE" "RIBBONSETTINGSENABLED" "RIBBONSTATE" "ROAMABLEROOTPREFIX"
    "ROLLOVEROPACITY" "ROLLOVERPARAMS" "ROLLOVERSELECTIONSET" "ROLLOVERTIPS"
    "RTDISPLAY" "RTISOLATESELECTION" "RTREGENAUTO" "RTROTATIONSPEEDFACTOR"
    "RUBBERBANDCOLOR" "RUBBERBANDSTYLE" "RUBBERSHEETSENSIBILITY_FOR_OS_X" "RUBBERSHEET_FOR_OS_X"
    "RULERDISPLAY" "RULERTEXTCOLOR" "RUNASLEVEL" "RVTRFALEVELOFDETAIL"
    "RVTVALIDATEBREP" "SAFEMODE" "SAVECHANGETOLAYOUT" "SAVEFIDELITY"
    "SAVEFILE" "SAVEFILEPATH" "SAVEFORMAT" "SAVELAYERSNAPSHOT"
    "SAVENAME" "SAVEONDOCSWITCH" "SAVEROUNDTRIP" "SAVETIME"
    "SCREENBOXES" "SCREENMODE" "SCREENSIZE" "SCRLHIST"
    "SDI" "SECTIONOFFSETINC" "SECTIONRESULTINTERVAL" "SECTIONSCALE"
    "SECTIONSETTINGSSEARCHPATH" "SECTIONSHEETSETTEMPLATEIMPERIAL" "SECTIONSHEETSETTEMPLATEMETRIC" "SECTIONTHICKNESSINC"
    "SECURELOAD" "SECUREREMOTEACCESS" "SELECTIONANNODISPLAY" "SELECTIONAREA"
    "SELECTIONAREAOPACITY" "SELECTIONCYCLING" "SELECTIONEFFECT" "SELECTIONEFFECTCOLOR"
    "SELECTIONMODES" "SELECTIONOFFSCREEN" "SELECTIONPREVIEW" "SELECTIONPREVIEWLIMIT"
    "SELECTSIMILARMODE" "SETBYLAYERMODE" "SHADEDGE" "SHADEDIF"
    "SHAREDVIEWSTATE" "SHAREVIEWPROPERTIES" "SHAREVIEWTYPE" "SHEETNUMBERLEADINGZEROES"
    "SHEETSETAUTOBACKUP" "SHEETSETTEMPLATEPATH" "SHORTCUTMENU" "SHORTCUTMENUDURATION"
    "SHOWDOCTABS" "SHOWFULLPATHINTITLE" "SHOWHIST" "SHOWIDSPROPERTIESONLY"
    "SHOWLAYERUSAGE" "SHOWNEWSTATE" "SHOWPALETTESTATE" "SHOWSCROLLBUTTONS"
    "SHOWTABCLOSEBUTTON" "SHOWTABCLOSEBUTTONACTIVE" "SHOWTABCLOSEBUTTONALL" "SHOWWINDOWLISTBUTTON"
    "SHPNAME" "SIGWARN" "SINGLETONMODE" "SITELOCATIONVISIBILITY"
    "SKETCHFEATURECOPYMODE" "SKETCHINC" "SKPOLY" "SKYSTATUS"
    "SMASSEMBLYEXPORTMODE" "SMASSEMBLYEXPORTREPORTPATHTYPE" "SMASSEMBLYEXPORTSOLIDTYPESINREPORTS" "SMATTRIBUTESLAYERCOLOR"
    "SMATTRIBUTESLAYERTEXTHEIGHT" "SMATTRIBUTESLAYERTEXTHEIGHTTYPE" "SMBENDANNOTATIONSLAYERCOLOR" "SMBENDANNOTATIONSLAYERTEXTHEIGHT"
    "SMBENDANNOTATIONSLAYERTEXTHEIGHTTYPE" "SMBENDLINESDOWNLAYERCOLOR" "SMBENDLINESDOWNLAYERLINETYPE" "SMBENDLINESDOWNLAYERLINEWEIGHT"
    "SMBENDLINESUPLAYERCOLOR" "SMBENDLINESUPLAYERLINETYPE" "SMBENDLINESUPLAYERLINEWEIGHT" "SMBEVELFEATURECOLOR"
    "SMCOLORBEND" "SMCOLORBENDRELIEF" "SMCOLORBEVEL" "SMCOLORCORNERRELIEF"
    "SMCOLORFLANGE" "SMCOLORFLANGEREFERENCESIDE" "SMCOLORFORM" "SMCOLORHEM"
    "SMCOLORJOG" "SMCOLORJUNCTION" "SMCOLORLOFTEDBEND" "SMCOLORMITER"
    "SMCOLORROLLEDEDGE" "SMCOLORTAB" "SMCOLORWRONGBEND" "SMCOLORWRONGFLANGE"
    "SMCONTOURSLAYERCOLOR" "SMCONTOURSLAYERLINETYPE" "SMCONTOURSLAYERLINEWEIGHT" "SMCONVERTMAXIMALBEVELANGLE"
    "SMCONVERTMINIMALBEVELANGLE" "SMCONVERTPREFERFORMFEATURES" "SMCONVERTPREFERHEMFEATURES" "SMCONVERTPREFERJOGFEATURES"
    "SMCONVERTPREFERZEROBENDFEATURES" "SMCONVERTRECOGNIZEBEVELS" "SMCONVERTRECOGNIZEHOLES" "SMCONVERTRECOGNIZERIBCONTROLCURVES"
    "SMCONVERTWRONGFEATURETHICKNESSDEVIATIONTYPE" "SMCONVERTWRONGFEATURETHICKNESSDEVIATIONVALUE" "SMDEFAULTBENDLINEEXTENTTYPE" "SMDEFAULTBENDLINEEXTENTVALUE"
    "SMDEFAULTBENDRADIUSTYPE" "SMDEFAULTBENDRADIUSVALUE" "SMDEFAULTBENDRELIEFWIDTHTYPE" "SMDEFAULTBENDRELIEFWIDTHVALUE"
    "SMDEFAULTBEVELFEATUREUNFOLDMODE" "SMDEFAULTCORNERRELIEFDIAMETERVALUE" "SMDEFAULTFLANGESPLITEXTENSIONTYPE" "SMDEFAULTFLANGESPLITEXTENSIONVALUE"
    "SMDEFAULTFLANGESPLITGAPTYPE" "SMDEFAULTFLANGESPLITGAPVALUE" "SMDEFAULTFORMFEATUREUNFOLDMODE" "SMDEFAULTGUSSETDEPTHTYPE"
    "SMDEFAULTGUSSETDEPTHVALUE" "SMDEFAULTGUSSETFILLETRADIUSTYPE" "SMDEFAULTGUSSETFILLETRADIUSVALUE" "SMDEFAULTGUSSETTYPE"
    "SMDEFAULTGUSSETWIDTHTYPE" "SMDEFAULTGUSSETWIDTHVALUE" "SMDEFAULTHEMGAPTYPE" "SMDEFAULTHEMGAPVALUE"
    "SMDEFAULTHEMRELATIVEBENDDEDUCTION" "SMDEFAULTJOGANGLEVALUE" "SMDEFAULTJOGHEIGHTTYPE" "SMDEFAULTJOGHEIGHTVALUE"
    "SMDEFAULTJOGRADIUSTYPE" "SMDEFAULTJOGRADIUSVALUE" "SMDEFAULTJUNCTIONALIGNMENTTORELIEF" "SMDEFAULTJUNCTIONGAPTYPE"
    "SMDEFAULTJUNCTIONGAPVALUE" "SMDEFAULTKFACTOR" "SMDEFAULTLOFTEDBENDNUMBERSAMPLES" "SMDEFAULTRELIEFEXTENSIONTYPE"
    "SMDEFAULTRELIEFEXTENSIONVALUE" "SMDEFAULTRIBFILLETRADIUSTYPE" "SMDEFAULTRIBFILLETRADIUSVALUE" "SMDEFAULTRIBPROFILERADIUSTYPE"
    "SMDEFAULTRIBPROFILERADIUSVALUE" "SMDEFAULTRIBROUNDRADIUSTYPE" "SMDEFAULTRIBROUNDRADIUSVALUE" "SMDEFAULTSHARPBENDRADIUSLIMITRATIO"
    "SMDEFAULTTABCHAMFERDISTANCETYPE" "SMDEFAULTTABCHAMFERDISTANCEVALUE" "SMDEFAULTTABCLEARANCETYPE" "SMDEFAULTTABCLEARANCEVALUE"
    "SMDEFAULTTABDISTANCETYPE" "SMDEFAULTTABDISTANCEVALUE" "SMDEFAULTTABEDGETYPE" "SMDEFAULTTABFILLETRADIUSTYPE"
    "SMDEFAULTTABFILLETRADIUSVALUE" "SMDEFAULTTABHEIGHTTYPE" "SMDEFAULTTABHEIGHTVALUE" "SMDEFAULTTABLENGTHTYPE"
    "SMDEFAULTTABLENGTHVALUE" "SMDEFAULTTABSLOTNUMBER" "SMDEFAULTTHICKNESS" "SMEXPORTOSMAPPROXIMATIONACCURACY"
    "SMEXPORTOSMMINIMALEDGELENGTH" "SMFORMFEATURESDOWNCOLOR" "SMFORMFEATURESDOWNLAYERLINETYPE" "SMFORMFEATURESDOWNLAYERLINEWEIGHT"
    "SMFORMFEATURESUPCOLOR" "SMFORMFEATURESUPLAYERLINETYPE" "SMFORMFEATURESUPLAYERLINEWEIGHT" "SMHEMCREATECLOSEDHEMGAP"
    "SMJUNCTIONCREATEHEALCOINCIDENT" "SMOOTHMESHCONVERT" "SMOOTHMESHGRID" "SMOOTHMESHMAXFACE"
    "SMOOTHMESHMAXLEV" "SMOVERALLANNOTATIONSLAYERCOLOR" "SMOVERALLANNOTATIONSLAYERLINETYPE" "SMOVERALLANNOTATIONSLAYERLINEWEIGHT"
    "SMPARAMETRIZEHOLESPARAMETRIZATION" "SMREPAIRLOFTEDBENDMERGE" "SMROLLEDEDGEANNOTATIONSLAYERCOLOR" "SMROLLEDEDGEANNOTATIONSLAYERTEXTHEIGHT"
    "SMROLLEDEDGEANNOTATIONSLAYERTEXTHEIGHTTYPE" "SMROLLEDEDGELINESDOWNLAYERCOLOR" "SMROLLEDEDGELINESDOWNLAYERLINETYPE" "SMROLLEDEDGELINESDOWNLAYERLINEWEIGHT"
    "SMROLLEDEDGELINESUPLAYERCOLOR" "SMROLLEDEDGELINESUPLAYERLINETYPE" "SMROLLEDEDGELINESUPLAYERLINEWEIGHT" "SMSMARTFEATURES"
    "SMSPLITAMBIGUOUSINPUT" "SMSPLITCONVERTBENDTOJUNCTION" "SMSPLITHEALCOINCIDENT" "SMSPLITORTHOGONALBENDSPLIT"
    "SMTARGETCAM" "SMUNFOLDAPPEARANCE" "SNAPANG" "SNAPBASE"
    "SNAPGRIDLEGACY" "SNAPISOPAIR" "SNAPMARKERCOLOR" "SNAPMARKERSIZE"
    "SNAPMARKERTHICKNESS" "SNAPMODE" "SNAPSTYL" "SNAPTYPE"
    "SNAPUNIT" "SOLIDCHECK" "SOLIDHIST" "SORTENTS"
    "SORTORDER" "SPAADJUSTMODE" "SPACESWITCH" "SPACHECKLEVEL"
    "SPAGRIDASPECTRATIO" "SPAGRIDMODE" "SPAMAXFACETEDGELENGTH" "SPAMAXNUMGRIDLINES"
    "SPAMINUGRIDLINES" "SPAMINVGRIDLINES" "SPANORMALTOL" "SPASURFACETOL"
    "SPATRIANGMODE" "SPAUSEFACETRES" "SPLDEGREE" "SPLFRAME"
    "SPLINESEGS" "SPLINETYPE" "SPLKNOTS" "SPLMETHOD"
    "SPLPERIODIC" "SRCHPATH" "SSFOUND" "SSLOCATE"
    "SSMAUTOOPEN" "SSMOPENMODE" "SSMPOLLTIME" "SSMSHEETSTATUS"
    "SSMSTATE" "STACKPANELTYPE" "STAMPFONTSIZE" "STAMPFONTSTYLE"
    "STAMPFOOTER" "STAMPFOOTEROFFSETX" "STAMPFOOTEROFFSETY" "STAMPHEADER"
    "STAMPHEADEROFFSETX" "STAMPHEADEROFFSETY" "STAMPUNITS" "STANDARDSOPTIONS"
    "STANDARDSVIOLATION" "STARTINFOLDER" "STARTMODE" "STARTUP"
    "STATUSBAR" "STEPSIZE" "STEPSPERSEC" "STLPOSITIVEQUADRANT"
    "STORYBAR" "STRUCTURETREECONFIG" "STUDENTDRAWING" "STYLUSFORCETHRESHOLD"
    "SUBOBJSELECTIONMODE" "SUNPROPERTIESSTATE" "SUNSTATUS" "SUPPRESSALERTS"
    "SURFACEASSOCIATIVITY" "SURFACEASSOCIATIVITYDRAG" "SURFACEAUTOTRIM" "SURFACEMODELINGMODE"
    "SURFTAB1" "SURFTAB2" "SURFTYPE" "SURFU"
    "SURFV" "SVGBLENDEDGRADIENTS" "SVGCOLORPOLICY" "SVGDEFAULTIMAGEEXTENSION"
    "SVGGENERICFONTFAMILY" "SVGIMAGEBASE" "SVGIMAGEURL" "SVGLINEWEIGHTSCALE"
    "SVGOUTPUTHEIGHT" "SVGOUTPUTWIDTH" "SVGPRECISION" "SVGSCALEFACTOR"
    "SYSCODEPAGE" "SYSFLOATING" "SYSMON" "TABCONTROLHEIGHT"
    "TABLEINDICATOR" "TABLELAYER" "TABLETOOLBAR" "TABMODE"
    "TABSFIXEDWIDTH" "TANGENTLENGTHTYPE" "TANGENTLENGTHVALUE" "TARGET"
    "TBCUSTOMIZE" "TBSHOWSHORTCUTS" "TDCREATE" "TDINDWG"
    "TDUCREATE" "TDUPDATE" "TDUSRTIMER" "TDUUPDATE"
    "TEETANGENTLENGTHTYPE" "TEETANGENTLENGTHVALUE" "TEMPLATEPATH" "TEMPOVERRIDES"
    "TEMPPREFIX" "TEXTALIGNMODE" "TEXTALIGNSPACING" "TEXTALLCAPS"
    "TEXTANGLE" "TEXTAUTOCORRECTCAPS" "TEXTED" "TEXTEDITMODE"
    "TEXTEVAL" "TEXTFILL" "TEXTGAPSELECTION" "TEXTJUSTIFY"
    "TEXTLAYER" "TEXTOUTPUTFILEFORMAT" "TEXTQLTY" "TEXTSIZE"
    "TEXTSTYLE" "TEXTTOATTRIBUTE" "TEXTUREMAPPATH" "THICKNESS"
    "THREADDISPLAY" "THUMBSAVE" "THUMBSIZE" "THUMBSIZE2D"
    "TILEMODE" "TILEMODELIGHTSYNCH" "TIMEZONE" "TOOLBARMARGIN"
    "TOOLBUTTONSIZE" "TOOLICONPADDING" "TOOLPALETTEPATH" "TOOLTIPDELAY"
    "TOOLTIPMERGE" "TOOLTIPS" "TOOLTIPTRANSPARENCY" "TOUCHMODE"
    "TPSTATE" "TRACECURRENT" "TRACEDISPLAYMODE" "TRACEFADECTL"
    "TRACEMARKUPFADECTL" "TRACEMODE" "TRACEOSNAP" "TRACEPALETTESTATE"
    "TRACEPAPERCTL" "TRACEVPSUPPORT" "TRACEWID" "TRACKPATH"
    "TRANSPARENCYDISPLAY" "TRAYICONS" "TRAYNOTIFY" "TRAYTIMEOUT"
    "TREEDEPTH" "TREEMAX" "TRIMEDGES" "TRIMEXTENDMODE"
    "TRIMMODE" "TRUSTEDPATHS" "TSPACEFAC" "TSPACETYPE"
    "TSTACKALIGN" "TSTACKSIZE" "TTFASTEXT" "TUTORIALSONSTARTPAGE"
    "UCS2DDISPLAYSETTING" "UCS3DPARADISPLAYSETTING" "UCS3DPERPDISPLAYSETTING" "UCSAXISANG"
    "UCSBASE" "UCSDETECT" "UCSFOLLOW" "UCSICON"
    "UCSICONPOS" "UCSNAME" "UCSORG" "UCSORTHO"
    "UCSSELECTMODE" "UCSVIEW" "UCSVP" "UCSXDIR"
    "UCSYDIR" "UNDOCTL" "UNDOMARKS" "UNITESURFACES"
    "UNITMODE" "UOSNAP" "UPDATETHUMBNAIL" "USECOMMUNICATOR"
    "USENEWSTATUSBAR" "USERI1" "USERI2" "USERI3"
    "USERI4" "USERI5" "USERR1" "USERR2"
    "USERR3" "USERR4" "USERR5" "USERS1"
    "USERS2" "USERS3" "USERS4" "USERS5"
    "USESTANDARDOPENFILEDIALOG" "VBAMACROS" "VENDORNAME" "VERBOSEBIMSECTIONUPDATE"
    "VERSIONCONTROLCONFIGPATH" "VERSIONCONTROLDOWNLOADPATH" "VERSIONCUSTOMIZABLEFILES" "VIEWBACKSTATUS"
    "VIEWCTR" "VIEWDIR" "VIEWFWDSTATUS" "VIEWMODE"
    "VIEWPORTLAYER" "VIEWSIZE" "VIEWSKETCHMODE" "VIEWTWIST"
    "VIEWUPDATEAUTO" "VISRETAIN" "VISRETAINMODE" "VOLUMEPREC"
    "VOLUMEUNITS" "VPCONTROL" "VPLAYEROVERRIDES" "VPLAYEROVERRIDESMODE"
    "VPMAXIMIZEDSTATE" "VPROTATEASSOC" "VSACURVATUREHIGH" "VSACURVATURELOW"
    "VSACURVATURETYPE" "VSADRAFTANGLEHIGH" "VSAZEBRACOLOR1" "VSAZEBRACOLOR2"
    "VSAZEBRADIRECTION" "VSAZEBRASIZE" "VSAZEBRATYPE" "VSBACKGROUNDS"
    "VSEDGECOLOR" "VSEDGEJITTER" "VSEDGELEX" "VSEDGES"
    "VSEDGESMOOTH" "VSFACECOLORMODE" "VSFACEHIGHLIGHT" "VSFACEOPACITY"
    "VSFACESTYLE" "VSHALOGAP" "VSINTERSECTIONCOLOR" "VSINTERSECTIONEDGES"
    "VSINTERSECTIONLTYPE" "VSISOONTOP" "VSLIGHTINGQUALITY" "VSMATERIALMODE"
    "VSMAX" "VSMIN" "VSMONOCOLOR" "VSOCCLUDEDCOLOR"
    "VSOCCLUDEDEDGES" "VSOCCLUDEDLTYPE" "VSSHADOWS" "VSSILHEDGES"
    "VSSILHWIDTH" "VSSTATE" "VTDURATION" "VTENABLE"
    "VTFPS" "WARNINGMESSAGES" "WBLOCKCREATEMODE" "WHIPARC"
    "WHIPTHREAD" "WINDOWAREACOLOR" "WIPEOUTFRAME" "WMFBKGND"
    "WMFFOREGND" "WMFTTFASTEXT" "WNDLMAIN" "WNDLSCRL"
    "WNDLTEXT" "WNDPMAIN" "WNDPTEXT" "WNDSMAIN"
    "WNDSTEXT" "WORKINGFOLDER" "WORKSPACELABEL" "WORLDUCS"
    "WORLDVIEW" "WRITESTAT" "WSAUTOSAVE" "WSCURRENT"
    "XCLIPFRAME" "XCOMPAREBAKPATH" "XCOMPAREBAKSIZE" "XCOMPARECOLORMODE"
    "XCOMPAREENABLE" "XDWGFADECTL" "XEDIT" "XFADECTL"
    "XLOADCTL" "XLOADPATH" "XNOTIFYTIME" "XREFCTL"
    "XREFLAYER" "XREFNOTIFY" "XREFOVERRIDE" "XREFREGAPPCTL"
    "XREFTYPE" "ZOOMFACTOR" "ZOOMWHEEL" "_TOOLPALETTEPATH"
  ))

(defun dump-sysvars-names ( )
  "Return the sorted list of known system-variable names."
  *dump-sysvars-names*)

(defun dump-sysvars ( filename / f count name )
  "Write every known system variable and its current value to
FILENAME, one variable per line, as

    \"NAME\" VALUE

using PRIN1 for both fields. Return the number of variables written,
or nil if FILENAME could not be opened for output."
  (setq f (open filename "w"))
  (if (null f)
      (progn
        (princ "dump-sysvars: cannot open file for writing: ")
        (princ filename)
        (princ "\n")
        nil)
      (progn
        (setq count 0)
        (foreach name *dump-sysvars-names*
          (prin1 name f)              ; "NAME" (quoted, via prin1)
          (princ " " f)
          (prin1 (getvar name) f)     ; VALUE  (quoted if a string)
          (princ "\n" f)
          (setq count (1+ count)))
        (close f)
        count)))

(princ)
