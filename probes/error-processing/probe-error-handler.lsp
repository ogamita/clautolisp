;; Error-handling probes (*error*, exit, vl-exit-with-error, command): one C:Pn command per case, run at top level from a script.
(setq plog-path (strcat *probe-dir* "/probe-log.txt"))
(defun plog (tag val / f)
  (setq f (open plog-path "a"))
  (write-line (strcat tag " = " (vl-prin1-to-string val)) f)
  (close f)
  val)
(plog "=== debut chargement" 1)

(defun msgof (thunk / r)
  (setq r (vl-catch-all-apply thunk nil))
  (if (vl-catch-all-error-p r)
    (list 'ERROR (vl-catch-all-error-message r))
    (list 'VALUE r)))

(defun global-handler (msg)
  (plog "  GLOBAL *error* appele, msg" msg)
  (princ))
(setq *error* global-handler)
(plog "=== handler global pose" 1)

;; P1 : motif schms_transaction_undo (setq global de *error*, variable locale capturee, push-error-using-stack)
(defun p1-transaction (f / sauvegarde p1loc)
  (setq sauvegarde *error*
        p1loc "LOCALE-P1")
  (setq *error* (lambda (msg)
                  (plog "  P1 handler appele, msg" msg)
                  (plog "  P1 handler voit p1loc" p1loc)
                  (plog "  P1 handler voit sauvegarde" (type sauvegarde))
                  (setq *error* sauvegarde)
                  (princ)))
  (*push-error-using-stack*)
  (f)
  (setq *error* sauvegarde)
  (*pop-error-mode*))
(defun c:P1 ()
  (plog "P1 debut" 1)
  (p1-transaction (lambda (/ x) (setq x 0) (/ 1 x)))
  (plog "P1 apres (ne doit pas s'afficher)" 1)
  (princ))
(defun c:P1B ()
  (plog "P1B *error* restaure apres P1 ?" (if (eq *error* global-handler) 'GLOBAL-HANDLER (type *error*)))
  (setq *error* global-handler)
  (princ))

;; P2 : idem sans *push-error-using-stack*
(defun p2-transaction (f / sauvegarde p2loc)
  (setq sauvegarde *error*
        p2loc "LOCALE-P2")
  (setq *error* (lambda (msg)
                  (plog "  P2 handler appele, msg" msg)
                  (plog "  P2 handler voit p2loc" p2loc)
                  (setq *error* sauvegarde)
                  (princ)))
  (f)
  (setq *error* sauvegarde))
(defun c:P2 ()
  (plog "P2 debut" 1)
  (p2-transaction (lambda () (strcat "a" nil)))
  (princ))
(defun c:P2B ()
  (plog "P2B *error* restaure apres P2 ?" (if (eq *error* global-handler) 'GLOBAL-HANDLER (type *error*)))
  (setq *error* global-handler)
  (princ))

;; P3 : *error* local dans une sous-fonction (motif `dialogue (/ id test *error*)`)
(defun p3-dialogue (/ id *error*)
  (defun *error* (msg)
    (plog "  P3 *error* LOCAL appele, msg" msg)
    (plog "  P3 local voit id" id)
    (princ))
  (setq id 42)
  (car 1))
(defun c:P3 ()
  (plog "P3 debut" 1)
  (p3-dialogue)
  (princ))

;; P4 : *error* local dans la commande, erreur profonde
(defun p4-profond (/ p4loc) (setq p4loc "PROFOND") (undefined-p4-fn))
(defun c:P4 (/ *error* p4cmd)
  (defun *error* (msg)
    (plog "  P4 *error* local commande, msg" msg)
    (plog "  P4 voit p4cmd" p4cmd)
    (plog "  P4 voit p4loc (sous-fonction)" p4loc)
    (princ))
  (setq p4cmd "CMD")
  (plog "P4 debut" 1)
  (p4-profond)
  (princ))

;; P5 : *error* appele a l'interieur de vl-catch-all-apply ?
(defun c:P5 (/ r)
  (plog "P5 debut" 1)
  (setq r (msgof (function (lambda () (/ 1 0)))))
  (plog "P5 resultat catch-all" r)
  (princ))

;; P6 : erreur dans le handler lui-meme
(defun c:P6 (/ *error*)
  (defun *error* (msg)
    (plog "  P6 handler appele, msg" msg)
    (strcat msg nil)
    (plog "  P6 handler fin (ne doit pas s'afficher)" 1)
    (princ))
  (plog "P6 debut" 1)
  (/ 1 0))

(plog "=== avant P7" 1)
;; P7 : catalogue de messages (via vl-catch-all-apply)
(defun c:P7 (/ doc lin)
  (setq doc (vla-get-activedocument (vlax-get-acad-object)))
  (plog "P7 (/ 1 0)" (msgof (function (lambda () (/ 1 0)))))
  (plog "P7 (strcat nil)" (msgof (function (lambda () (strcat "a" nil)))))
  (plog "P7 (car 1)" (msgof (function (lambda () (car 1)))))
  (plog "P7 fonction indefinie" (msgof (function (lambda () (pas-definie-p7)))))
  (plog "P7 (exit)" (msgof (function (lambda () (exit)))))
  (plog "P7 (quit)" (msgof (function (lambda () (quit)))))
  (plog "P7 (error \"x\")" (msgof (function (lambda () (error "x")))))
  (plog "P7 vla-item bloc inexistant" (msgof (function (lambda () (vla-item (vla-get-blocks doc) "PAS_DE_BLOC_P7")))))
  (plog "P7 (command \"_NOSUCHCMD\")" (msgof (function (lambda () (command "_NOSUCHCMD")))))
  (plog "P7 (command-s \"_NOSUCHCMD\")" (msgof (function (lambda () (command-s "_NOSUCHCMD")))))
  (plog "P7 (command \"_LINE\" nil-point)" (msgof (function (lambda () (command "_LINE" "pas-un-point" "")))))
  (plog "P7 (command-s \"_LINE\" bad)" (msgof (function (lambda () (command-s "_LINE" "pas-un-point" "")))))
  (setq lin (entmakex '((0 . "LINE") (10 0.0 0.0 0.0) (11 10.0 0.0 0.0))))
  (plog "P7 curve getPointAtDist hors courbe" (msgof (function (lambda () (vlax-curve-getPointAtDist lin 25.0)))))
  (plog "P7 curve getPointAtParam hors courbe" (msgof (function (lambda () (vlax-curve-getPointAtParam lin 25.0)))))
  (plog "P7 curve getParamAtPoint hors courbe" (msgof (function (lambda () (vlax-curve-getParamAtPoint lin '(5.0 3.0 0.0))))))
  (plog "P7 curve getDistAtPoint hors courbe" (msgof (function (lambda () (vlax-curve-getDistAtPoint lin '(5.0 3.0 0.0))))))
  (plog "P7 curve getPointAtDist nil" (msgof (function (lambda () (vlax-curve-getPointAtDist lin nil)))))
  (plog "P7 curve getClosestPointTo nil" (msgof (function (lambda () (vlax-curve-getClosestPointTo lin nil)))))
  (plog "P7 entmakex LINE avec (10) vide" (msgof (function (lambda () (entmakex (list '(0 . "LINE") (cons 10 nil) '(11 5.0 5.0 0.0)))))))
  (plog "P7 polar nil" (msgof (function (lambda () (polar nil 0.0 1.0)))))
  (plog "P7 distance nil" (msgof (function (lambda () (distance nil '(1 1 0))))))
  (plog "P7 inters nil" (msgof (function (lambda () (inters nil '(1 1) '(0 1) '(1 0))))))
  (princ))

(plog "=== avant P8" 1)
;; P8 : erreur dans une commande appelee depuis une autre via (command)
(defun c:P8INNER () (plog "  P8INNER debut" 1) (/ 1 0) (princ))
(defun c:P8 (/ *error*)
  (defun *error* (msg) (plog "  P8 handler externe, msg" msg) (princ))
  (plog "P8 debut" 1)
  (c:P8INNER)
  (plog "P8 apres (ne doit pas s'afficher)" 1)
  (princ))

;; P9 : (exit) dans une commande -> message recu par *error*
(defun c:P9 (/ *error*)
  (defun *error* (msg) (plog "  P9 handler msg de (exit)" msg) (princ))
  (plog "P9 debut" 1)
  (exit))

;; P10 : vl-exit-with-error dans une commande (hors VLX)
(defun c:P10 (/ *error*)
  (defun *error* (msg) (plog "  P10 handler msg vl-exit-with-error" msg) (princ))
  (plog "P10 debut" 1)
  (vl-exit-with-error "message-p10"))

;; P11 : commande invalide hors vl-catch-all-apply : *error* appele ? execution continue ?
(defun c:P11 (/ *error*)
  (defun *error* (msg) (plog "  P11 handler msg command invalide" msg) (princ))
  (plog "P11 debut" 1)
  (command "_LINE" "pas-un-point" "")
  (plog "P11 apres command (continue)" (getvar "CMDACTIVE"))
  (command-s "_LINE" "pas-un-point" "")
  (plog "P11 apres command-s (continue)" (getvar "CMDACTIVE"))
  (princ))

;; P12 : (error "x") dans une commande -> message recu par *error*
(defun c:P12 (/ *error*)
  (defun *error* (msg) (plog "  P12 handler msg de (error)" msg) (princ))
  (plog "P12 debut" 1)
  (error "message-p12"))

;; P1F : variante, thunk passe par (function (lambda ...)) puis appele (f)
(defun c:P1F ()
  (plog "P1F debut" 1)
  (p2-transaction (function (lambda () (strcat "a" nil))))
  (princ))

;; P13 : command-s sur entree refusee, en tete de commande (hors vl-catch-all-apply)
(defun c:P13 (/ *error*)
  (defun *error* (msg) (plog "  P13 handler msg command-s refusee" msg) (princ))
  (plog "P13 debut" 1)
  (plog "P13 resultat command-s" (command-s "_LINE" "pas-un-point" ""))
  (plog "P13 apres command-s (continue)" (getvar "CMDACTIVE"))
  (princ))

;; P14 : la meme, sous vl-catch-all-apply direct (sans READ/EVAL)
(defun c:P14 (/ *error* r)
  (defun *error* (msg) (plog "  P14 handler msg" msg) (princ))
  (plog "P14 debut" 1)
  (setq r (vl-catch-all-apply 'command-s (list "_LINE" "pas-un-point" "")))
  (plog "P14 resultat" (if (vl-catch-all-error-p r) (list 'ERROR (vl-catch-all-error-message r)) r))
  (princ))

(plog "=== charge" (list (getvar "VENDORNAME") (getvar "ACADVER") (getvar "LOCALE")))
(princ)
